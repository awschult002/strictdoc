[DOCUMENT]
TITLE: Document 1

[GRAMMAR]
ELEMENTS:
- TAG: REQUIREMENT
  FIELDS:
  - TITLE: UID
    TYPE: String
    REQUIRED: False
  - TITLE: TITLE
    TYPE: String
    REQUIRED: False
  RELATIONS:
  - TYPE: Parent
  - TYPE: Child

[REQUIREMENT]
UID: REQ-1
TITLE: Parent requirement
RELATIONS:
- TYPE: Child
  VALUE: REQ-2

[REQUIREMENT]
UID: REQ-2
TITLE: Child requirement
