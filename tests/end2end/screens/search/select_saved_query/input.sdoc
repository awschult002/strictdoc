[DOCUMENT]
TITLE: Document 1

[REQUIREMENT]
UID: REQ-1
TITLE: System requirement
STATEMENT: System requirement statement.

[REQUIREMENT]
UID: REQ-2
TITLE: Logging requirement
STATEMENT: Logging requirement statement.
