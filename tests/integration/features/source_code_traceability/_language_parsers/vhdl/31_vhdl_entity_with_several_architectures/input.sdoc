[DOCUMENT]
TITLE: Hello world doc

[REQUIREMENT]
UID: REQ-1
TITLE: Requirement Title #1
STATEMENT: Requirement Statement #1

[REQUIREMENT]
UID: REQ-2
TITLE: Requirement Title #2
STATEMENT: Requirement Statement #2

[REQUIREMENT]
UID: REQ-3
TITLE: Requirement Title #3
STATEMENT: Requirement Statement #3
RELATIONS:
- TYPE: File
  VALUE: file.vhd
  FUNCTION: counter(sim).p
