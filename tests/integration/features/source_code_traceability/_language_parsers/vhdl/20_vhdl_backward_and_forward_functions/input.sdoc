[DOCUMENT]
TITLE: Reproducer

[GRAMMAR]
ELEMENTS:
- TAG: REQUIREMENT
  FIELDS:
  - TITLE: MID
    TYPE: String
    REQUIRED: False
  - TITLE: UID
    TYPE: String
    REQUIRED: False
  - TITLE: TITLE
    TYPE: String
    REQUIRED: False
  - TITLE: STATEMENT
    TYPE: String
    REQUIRED: False
  RELATIONS:
  - TYPE: File
    ROLE: Implementation
  - TYPE: File
    ROLE: Test
  - TYPE: File

[REQUIREMENT]
UID: REQ-1
TITLE: Requirement 1
STATEMENT: REQ-1 references forward to file.vhd:foo by file relation.
RELATIONS:
- TYPE: File
  VALUE: file.vhd

[REQUIREMENT]
UID: REQ-2
TITLE: Requirement 2
STATEMENT: >>>
file.vhd:foo references "backward" to REQ-2 by function annotation
in VHDL comment.
<<<

[REQUIREMENT]
UID: REQ-3
TITLE: Requirement 3
STATEMENT: >>>
file.vhd:foo references "backward" to REQ-3 by function annotation
in VHDL comment.
<<<

[REQUIREMENT]
UID: REQ-4
TITLE: Requirement 4
STATEMENT: >>>
next req
<<<
